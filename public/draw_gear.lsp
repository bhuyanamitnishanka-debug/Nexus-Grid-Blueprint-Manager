;;; AutoLISP Parametric Gear Drawing Script
(defun c:DrawNexusGear ( / centerPt extRadius intRadius teethCount angIncrement curAng i pt1 pt2 pt3 oldCmdEcho )
  (vl-load-com)
  (setq oldCmdEcho (getvar "CMDECHO"))
  (setvar "CMDECHO" 0)
  (setq centerPt '(0.0 0.0 0.0))
  (setq extRadius 12.5)
  (setq intRadius 9.5)
  (setq teethCount 24)
  (setq angIncrement (/ (* 2.0 pi) teethCount))
  (setq curAng 0.0)
  (setq i 0)
  (while (< i teethCount)
    (setq pt1 (polar centerPt curAng extRadius))
    (setq pt2 (polar centerPt (+ curAng (/ angIncrement 2.0)) intRadius))
    (setq pt3 (polar centerPt (+ curAng angIncrement) extRadius))
    (command "_.line" "_non" pt1 "_non" pt2 "")
    (command "_.line" "_non" pt2 "_non" pt3 "")
    (setq curAng (+ curAng angIncrement))
    (setq i (1+ i))
  )
  (command "_.circle" "_non" centerPt intRadius)
  (setvar "CMDECHO" oldCmdEcho)
  (princ "\n[*] AutoLISP Core Loaded & Parametric Micro-Gear Drafted Successfully.")
  (princ)
)
